;;; crystallization_area_pid_2d.lsp
;;; Compact conceptual 2D P&ID generator for AutoCAD / AutoCAD Plant 3D 2025.
;;; Command: PIDCRYSTAL2D
;;; Scope: Crystallization B/C and Final Molasses Area 302-319.
;;; IMPORTANT: 2D manual P&ID symbols only. No Plant 3D intelligent database
;;; objects and no 3D solids/commands are created.

(vl-load-com)

(setq *pid-assumption-note* "Literature-based assumed value; verify with actual plant/process data.")

(defun pid:pt (x y) (list (float x) (float y) 0.0))
(defun pid:deg (a) (* pi (/ a 180.0)))
(defun pid:set-layer (lay) (setvar "CLAYER" lay))

(defun pid:ensure-linetype (lt /)
  (if (and lt (/= (strcase lt) "CONTINUOUS") (not (tblsearch "LTYPE" lt)))
    (vl-catch-all-apply 'vl-cmdf (list "_.-LINETYPE" "_Load" lt "acad.lin" ""))
  )
)

(defun pid:lineweight-code (lw / val)
  (setq val (fix (+ 0.5 (* 100.0 (atof lw)))))
  (if (> val 0) val -3)
)

(defun pid:replace-dxf (code value data / found result pair)
  (setq found nil result nil)
  (foreach pair data
    (if (= (car pair) code)
      (progn (setq result (cons (cons code value) result)) (setq found T))
      (setq result (cons pair result))
    )
  )
  (if found (reverse result) (reverse (cons (cons code value) result)))
)

(defun pid:make-layer (name color ltype lw / obj data lwcode)
  (pid:ensure-linetype ltype)
  (setq lwcode (pid:lineweight-code lw))
  (if (setq obj (tblobjname "LAYER" name))
    (progn
      (setq data (entget obj))
      (setq data (pid:replace-dxf 62 color data))
      (setq data (pid:replace-dxf 6 ltype data))
      (setq data (pid:replace-dxf 370 lwcode data))
      (entmod data)
      (entupd obj)
    )
    (entmakex
      (list '(0 . "LAYER") '(100 . "AcDbSymbolTableRecord") '(100 . "AcDbLayerTableRecord")
            (cons 2 name) '(70 . 0) (cons 62 color) (cons 6 ltype) (cons 370 lwcode))
    )
  )
)

(defun pid:setup-layers (/)
  ;; Colors chosen for black AutoCAD background: white/cyan/green/magenta/red/orange.
  (pid:make-layer "PID_EQUIPMENT" 7 "CONTINUOUS" "0.30")
  (pid:make-layer "PID_PROCESS_LINE" 4 "CONTINUOUS" "0.35")
  (pid:make-layer "PID_UTILITY_LINE" 3 "DASHED" "0.25")
  (pid:make-layer "PID_INSTRUMENT" 6 "CONTINUOUS" "0.18")
  (pid:make-layer "PID_SIGNAL" 6 "DASHED" "0.18")
  (pid:make-layer "PID_VALVE" 1 "CONTINUOUS" "0.25")
  (pid:make-layer "PID_TEXT" 7 "CONTINUOUS" "0.18")
  (pid:make-layer "PID_TITLE_BLOCK" 8 "CONTINUOUS" "0.25")
  (pid:make-layer "PID_BOUNDARY" 8 "CONTINUOUS" "0.25")
  (pid:make-layer "PID_TABLE" 7 "CONTINUOUS" "0.18")
  (pid:make-layer "PID_SAFETY" 30 "CONTINUOUS" "0.25")
)

(defun pid:line (p1 p2 lay /)
  (pid:set-layer lay)
  (entmakex (list '(0 . "LINE") (cons 8 lay) (cons 10 p1) (cons 11 p2)))
)
(defun pid:circle (cen rad lay /)
  (pid:set-layer lay)
  (entmakex (list '(0 . "CIRCLE") (cons 8 lay) (cons 10 cen) (cons 40 rad)))
)
(defun pid:arc (cen rad a1 a2 lay /)
  (pid:set-layer lay)
  (entmakex (list '(0 . "ARC") (cons 8 lay) (cons 10 cen) (cons 40 rad) (cons 50 a1) (cons 51 a2)))
)
(defun pid:pline (pts lay closed / data)
  (pid:set-layer lay)
  (setq data (list '(0 . "LWPOLYLINE") '(100 . "AcDbEntity") (cons 8 lay)
                   '(100 . "AcDbPolyline") (cons 90 (length pts)) (cons 70 (if closed 1 0))))
  (foreach p pts (setq data (append data (list (cons 10 (list (car p) (cadr p)))))))
  (entmakex data)
)
(defun pid:rect (x1 y1 x2 y2 lay /)
  (pid:pline (list (pid:pt x1 y1) (pid:pt x2 y1) (pid:pt x2 y2) (pid:pt x1 y2)) lay T)
)
(defun pid:text (pt h str lay /)
  (pid:set-layer lay)
  (entmakex (list '(0 . "TEXT") (cons 8 lay) (cons 10 pt) (cons 40 h) (cons 1 str)
                  '(50 . 0.0) '(7 . "Standard") '(72 . 0) '(73 . 0)))
)
(defun pid:mtext (pt w h str lay /)
  (pid:set-layer lay)
  (entmakex (list '(0 . "MTEXT") (cons 8 lay) (cons 10 pt) (cons 40 h) (cons 41 w)
                  (cons 1 str) '(7 . "Standard") '(71 . 1))))

(defun pid:block-start (name / obj made)
  ;; Rebuild blocks on every run so older oversized block definitions are not reused.
  ;; If AutoCAD refuses to delete an old referenced block, skip redefining that block
  ;; rather than leaking symbol geometry into model space.
  (if (setq obj (tblobjname "BLOCK" name))
    (vl-catch-all-apply 'entdel (list obj))
  )
  (if (not (tblsearch "BLOCK" name))
    (setq made (entmakex (list '(0 . "BLOCK") (cons 2 name) '(70 . 0) (cons 10 (pid:pt 0 0)))))
  )
  (if made T nil)
)
(defun pid:block-end () (entmakex '((0 . "ENDBLK"))))

(defun pid:define-blocks (/)
  (if (pid:block-start "BLK_PID_VERTICAL_TANK")
    (progn (pid:rect -7 -11 7 11 "PID_EQUIPMENT") (pid:arc (pid:pt 0 11) 7 0 pi "PID_EQUIPMENT") (pid:arc (pid:pt 0 -11) 7 pi (* 2 pi) "PID_EQUIPMENT") (pid:line (pid:pt -5 -11) (pid:pt -8 -15) "PID_EQUIPMENT") (pid:line (pid:pt 5 -11) (pid:pt 8 -15) "PID_EQUIPMENT") (pid:block-end)))
  (if (pid:block-start "BLK_PID_VACUUM_CRYSTALLIZER")
    (progn (pid:rect -9 -12 9 12 "PID_EQUIPMENT") (pid:arc (pid:pt 0 12) 9 0 pi "PID_EQUIPMENT") (pid:arc (pid:pt 0 -12) 9 pi (* 2 pi) "PID_EQUIPMENT") (pid:line (pid:pt -9 3) (pid:pt 9 3) "PID_EQUIPMENT") (pid:line (pid:pt -9 -4) (pid:pt 9 -4) "PID_EQUIPMENT") (pid:line (pid:pt 0 20) (pid:pt 0 12) "PID_EQUIPMENT") (pid:block-end)))
  (if (pid:block-start "BLK_PID_CENTRIFUGE")
    (progn (pid:circle (pid:pt 0 0) 10 "PID_EQUIPMENT") (pid:circle (pid:pt 0 0) 5 "PID_EQUIPMENT") (pid:line (pid:pt -8 -6) (pid:pt 8 6) "PID_EQUIPMENT") (pid:line (pid:pt -8 6) (pid:pt 8 -6) "PID_EQUIPMENT") (pid:block-end)))
  (if (pid:block-start "BLK_PID_DRYER")
    (progn (pid:rect -13 -6 13 6 "PID_EQUIPMENT") (pid:line (pid:pt -10 -6) (pid:pt -5 6) "PID_EQUIPMENT") (pid:line (pid:pt 0 -6) (pid:pt 5 6) "PID_EQUIPMENT") (pid:line (pid:pt 8 -6) (pid:pt 13 6) "PID_EQUIPMENT") (pid:block-end)))
  (if (pid:block-start "BLK_PID_COOLER")
    (progn (pid:rect -11 -6 11 6 "PID_EQUIPMENT") (pid:line (pid:pt -11 0) (pid:pt 11 0) "PID_EQUIPMENT") (pid:line (pid:pt -5 -6) (pid:pt -5 6) "PID_EQUIPMENT") (pid:line (pid:pt 5 -6) (pid:pt 5 6) "PID_EQUIPMENT") (pid:block-end)))
  (if (pid:block-start "BLK_PID_MANUAL_VALVE")
    (progn (pid:pline (list (pid:pt -4 -3) (pid:pt 0 0) (pid:pt -4 3)) "PID_VALVE" T) (pid:pline (list (pid:pt 4 -3) (pid:pt 0 0) (pid:pt 4 3)) "PID_VALVE" T) (pid:block-end)))
  (if (pid:block-start "BLK_PID_CONTROL_VALVE")
    (progn (pid:pline (list (pid:pt -5 -3) (pid:pt 0 0) (pid:pt -5 3)) "PID_VALVE" T) (pid:pline (list (pid:pt 5 -3) (pid:pt 0 0) (pid:pt 5 3)) "PID_VALVE" T) (pid:line (pid:pt 0 0) (pid:pt 0 8) "PID_VALVE") (pid:circle (pid:pt 0 10) 2.5 "PID_VALVE") (pid:block-end)))
  (if (pid:block-start "BLK_PID_CHECK_VALVE")
    (progn (pid:pline (list (pid:pt -5 -4) (pid:pt 5 0) (pid:pt -5 4)) "PID_VALVE" T) (pid:line (pid:pt 6 -4) (pid:pt 6 4) "PID_VALVE") (pid:block-end)))
  (if (pid:block-start "BLK_PID_INSTRUMENT_BUBBLE") (progn (pid:circle (pid:pt 0 0) 5 "PID_INSTRUMENT") (pid:block-end)))
  (if (pid:block-start "BLK_PID_OFFPAGE_CONNECTOR")
    (progn (pid:pline (list (pid:pt -12 -5) (pid:pt 7 -5) (pid:pt 13 0) (pid:pt 7 5) (pid:pt -12 5)) "PID_BOUNDARY" T) (pid:block-end)))
  (if (pid:block-start "BLK_PID_FLOW_ARROW") (progn (pid:pline (list (pid:pt -3 -2) (pid:pt 4 0) (pid:pt -3 2)) "PID_PROCESS_LINE" T) (pid:block-end)))
  (if (pid:block-start "BLK_PID_SAMPLE_POINT") (progn (pid:circle (pid:pt 0 0) 2 "PID_SAFETY") (pid:line (pid:pt 0 0) (pid:pt 0 -6) "PID_SAFETY") (pid:block-end)))
  (if (pid:block-start "BLK_PID_DRAIN") (progn (pid:line (pid:pt 0 0) (pid:pt 0 -7) "PID_SAFETY") (pid:pline (list (pid:pt -4 -7) (pid:pt 4 -7) (pid:pt 0 -11)) "PID_SAFETY" T) (pid:block-end)))
  (if (pid:block-start "BLK_PID_VENT") (progn (pid:line (pid:pt 0 0) (pid:pt 0 7) "PID_SAFETY") (pid:arc (pid:pt 0 9) 2 0 pi "PID_SAFETY") (pid:block-end)))
  (if (pid:block-start "BLK_PID_PSV") (progn (pid:circle (pid:pt 0 0) 4 "PID_SAFETY") (pid:pline (list (pid:pt -3 -1) (pid:pt 0 3) (pid:pt 3 -1)) "PID_SAFETY" T) (pid:block-end)))
  (if (pid:block-start "BLK_PID_VACUUM_BREAKER") (progn (pid:circle (pid:pt 0 0) 4 "PID_SAFETY") (pid:text (pid:pt -2 -1.2) 2 "VB" "PID_SAFETY") (pid:block-end)))
)

(defun pid:insert (name pt sx sy rot lay /)
  (pid:set-layer lay)
  (entmakex (list '(0 . "INSERT") (cons 8 lay) (cons 2 name) (cons 10 pt) (cons 41 sx) (cons 42 sy) (cons 43 1.0) (cons 50 rot)))
)
(defun pid:tag (x y tag name /)
  (pid:text (pid:pt (- x 10) (- y 18)) 3.0 tag "PID_TEXT")
  (pid:text (pid:pt (- x 17) (- y 23)) 2.5 name "PID_TEXT")
)
(defun pid:inst (x y tag /)
  (pid:insert "BLK_PID_INSTRUMENT_BUBBLE" (pid:pt x y) 1 1 0 "PID_INSTRUMENT")
  (pid:text (pid:pt (- x 4.5) (- y 1.3)) 2.2 tag "PID_INSTRUMENT")
)
(defun pid:valve (x y tag rot ctrl /)
  (pid:insert (if ctrl "BLK_PID_CONTROL_VALVE" "BLK_PID_MANUAL_VALVE") (pid:pt x y) 1 1 rot "PID_VALVE")
  (pid:text (pid:pt (- x 6) (+ y 5)) 2.3 tag "PID_VALVE")
)
(defun pid:opcon (x y txt /)
  (pid:insert "BLK_PID_OFFPAGE_CONNECTOR" (pid:pt x y) 1 1 0 "PID_BOUNDARY")
  (pid:mtext (pid:pt (- x 11) (+ y 3)) 45 2.5 txt "PID_TEXT")
)
(defun pid:arrow-at (p1 p2 / x1 y1 x2 y2 ang)
  (setq x1 (car p1) y1 (cadr p1) x2 (car p2) y2 (cadr p2))
  (setq ang (atan (- y2 y1) (- x2 x1)))
  (pid:insert "BLK_PID_FLOW_ARROW" (pid:pt (/ (+ x1 x2) 2.0) (/ (+ y1 y2) 2.0)) 1 1 ang "PID_PROCESS_LINE")
)
(defun pid:path-line (pts lay / p1 p2)
  (setq p1 nil)
  (foreach p2 pts (if p1 (pid:line p1 p2 lay)) (setq p1 p2))
)
(defun pid:process-line (pts lineNo service labelx labely / segp1 segp2)
  (pid:path-line pts "PID_PROCESS_LINE")
  (setq segp1 (car pts) segp2 (cadr pts))
  (if (and (= (car segp1) (car segp2)) (> (length pts) 2)) (setq segp1 (cadr pts) segp2 (caddr pts)))
  (pid:arrow-at segp1 segp2)
  (pid:text (pid:pt labelx labely) 3.0 (strcat lineNo "  " service) "PID_TEXT")
)
(defun pid:utility-line (pts label x y /)
  (pid:path-line pts "PID_UTILITY_LINE")
  (if (> (length pts) 1) (pid:arrow-at (car pts) (cadr pts)))
  (pid:text (pid:pt x y) 2.5 label "PID_TEXT")
)
(defun pid:signal (pts /) (pid:path-line pts "PID_SIGNAL"))
(defun pid:control-station (x y tag /)
  ;; Simplified engineering-readable control valve: one clear symbol only.
  (pid:valve x y tag 0 T)
)


(defun pid:draw-equipment (/)
  ;; Expanded readable layout: B line, C line, and final molasses branch.
  (pid:opcon 20 220 "FROM CF-301 / MOLASSES A")
  (pid:insert "BLK_PID_VERTICAL_TANK" (pid:pt 75 220) 1 1 0 "PID_EQUIPMENT") (pid:tag 75 220 "TK-302" "Molasses A Tank")
  (pid:insert "BLK_PID_VACUUM_CRYSTALLIZER" (pid:pt 145 220) 1 1 0 "PID_EQUIPMENT") (pid:tag 145 220 "CR-302" "Vacuum Crystallizer B")
  (pid:insert "BLK_PID_CENTRIFUGE" (pid:pt 220 220) 1 1 0 "PID_EQUIPMENT") (pid:tag 220 220 "CF-302" "Centrifuge B")
  (pid:insert "BLK_PID_DRYER" (pid:pt 285 220) 1 1 0 "PID_EQUIPMENT") (pid:tag 285 220 "DR-302" "Dryer B")
  (pid:insert "BLK_PID_COOLER" (pid:pt 345 220) 1 1 0 "PID_EQUIPMENT") (pid:tag 345 220 "CL-302" "Cooler B")
  (pid:opcon 405 220 "TO GRADE SUGAR B")

  (pid:insert "BLK_PID_VERTICAL_TANK" (pid:pt 75 135) 1 1 0 "PID_EQUIPMENT") (pid:tag 75 135 "TK-303" "Molasses B Tank")
  (pid:insert "BLK_PID_VACUUM_CRYSTALLIZER" (pid:pt 145 135) 1 1 0 "PID_EQUIPMENT") (pid:tag 145 135 "CR-303" "Vacuum Crystallizer C")
  (pid:insert "BLK_PID_CENTRIFUGE" (pid:pt 220 135) 1 1 0 "PID_EQUIPMENT") (pid:tag 220 135 "CF-303" "Centrifuge C")
  (pid:insert "BLK_PID_DRYER" (pid:pt 285 135) 1 1 0 "PID_EQUIPMENT") (pid:tag 285 135 "DR-303" "Dryer C")
  (pid:insert "BLK_PID_COOLER" (pid:pt 345 135) 1 1 0 "PID_EQUIPMENT") (pid:tag 345 135 "CL-303" "Cooler C")
  (pid:opcon 405 135 "TO GRADE SUGAR C")

  (pid:insert "BLK_PID_VERTICAL_TANK" (pid:pt 220 55) 1 1 0 "PID_EQUIPMENT") (pid:tag 220 55 "TK-304" "Final Molasses Tank")
  (pid:opcon 350 55 "TO FINAL MOLASSES STORAGE")
)


(defun pid:draw-process (/)
  ;; Process flow relationship unchanged; labels are offset away from process lines.
  (pid:process-line (list (pid:pt 33 220) (pid:pt 66 220)) "S-309" "Molasses A" 35 231)
  (pid:valve 50 220 "HV-302A" 0 nil)
  (pid:process-line (list (pid:pt 84 220) (pid:pt 136 220)) "S-310" "Molasses A Feed" 90 235)
  (pid:control-station 105 220 "FCV-302")
  (pid:process-line (list (pid:pt 154 220) (pid:pt 210 220)) "S-311" "Massecuite B" 162 235)
  (pid:valve 185 220 "HV-302C" 0 nil)
  (pid:process-line (list (pid:pt 230 220) (pid:pt 272 220)) "S-312" "Wet Sugar B" 235 235)
  (pid:process-line (list (pid:pt 298 220) (pid:pt 334 220)) "S-313" "Dry Sugar B" 303 235)
  (pid:process-line (list (pid:pt 356 220) (pid:pt 392 220)) "S-314" "Grade Sugar B" 360 235)

  (pid:process-line (list (pid:pt 220 210) (pid:pt 220 180) (pid:pt 75 180) (pid:pt 75 146)) "S-315" "Molasses B" 112 187)
  (pid:valve 148 180 "HV-303A" 0 nil)
  (pid:process-line (list (pid:pt 84 135) (pid:pt 136 135)) "S-316" "Molasses B Feed" 88 124)
  (pid:control-station 105 135 "FCV-303")
  (pid:process-line (list (pid:pt 154 135) (pid:pt 210 135)) "S-317" "Massecuite C" 162 124)
  (pid:valve 185 135 "HV-303C" 0 nil)
  (pid:process-line (list (pid:pt 230 135) (pid:pt 272 135)) "S-318" "Wet Sugar C" 235 124)
  (pid:process-line (list (pid:pt 298 135) (pid:pt 334 135) (pid:pt 392 135)) "S-319" "Dry Sugar C / Grade Sugar C" 300 124)

  (pid:process-line (list (pid:pt 220 125) (pid:pt 220 66)) "S-320" "Final Molasses" 229 93)
  (pid:process-line (list (pid:pt 229 55) (pid:pt 337 55)) "S-320" "Final Molasses Storage" 258 67)
  (pid:control-station 286 55 "LCV-304")

  ;; Manual isolation, drains, vents, samples, and safety points are offset from tags.
  (pid:valve 92 220 "HV-302B" 0 nil) (pid:valve 92 135 "HV-303B" 0 nil)
  (pid:valve 242 55 "HV-304B" 0 nil) (pid:valve 220 96 "HV-304A" (pid:deg 90) nil)
  (foreach sp '((112 232 "SP-302") (118 188 "SP-303") (258 68 "SP-304"))
    (pid:insert "BLK_PID_SAMPLE_POINT" (pid:pt (car sp) (cadr sp)) 1 1 0 "PID_SAFETY")
    (pid:text (pid:pt (+ (car sp) 4) (+ (cadr sp) 3)) 2.5 (caddr sp) "PID_SAFETY"))
  (foreach dr '((75 207 "DV-302") (75 122 "DV-303") (220 42 "DV-304") (145 205 "DV-CR302") (145 120 "DV-CR303"))
    (pid:insert "BLK_PID_DRAIN" (pid:pt (car dr) (cadr dr)) 1 1 0 "PID_SAFETY")
    (pid:text (pid:pt (+ (car dr) 4) (- (cadr dr) 9)) 2.5 (caddr dr) "PID_SAFETY"))
  (pid:insert "BLK_PID_VENT" (pid:pt 220 68) 1 1 0 "PID_SAFETY") (pid:text (pid:pt 226 73) 2.5 "VV-304" "PID_SAFETY")
  (pid:insert "BLK_PID_PSV" (pid:pt 237 68) 1 1 0 "PID_SAFETY") (pid:text (pid:pt 243 73) 2.5 "PSV/VV-304" "PID_SAFETY")
)


(defun pid:draw-utilities (/)
  ;; Utility/off-page connectors are pulled away from equipment to reduce crowding.
  (pid:opcon 145 305 "TO VACUUM SYSTEM / CONDENSER")
  (pid:utility-line (list (pid:pt 145 240) (pid:pt 145 292)) "CR-302 VAPOR / VACUUM" 154 276)
  (pid:control-station 145 282 "PCV-302")
  (pid:insert "BLK_PID_VACUUM_BREAKER" (pid:pt 132 246) 1 1 0 "PID_SAFETY") (pid:text (pid:pt 110 252) 2.5 "VB/PSV-302" "PID_SAFETY")

  (pid:opcon 210 305 "TO VACUUM SYSTEM / CONDENSER")
  (pid:utility-line (list (pid:pt 145 155) (pid:pt 145 298) (pid:pt 210 298)) "CR-303 VAPOR / VACUUM" 154 162)
  (pid:control-station 190 298 "PCV-303")
  (pid:insert "BLK_PID_VACUUM_BREAKER" (pid:pt 132 157) 1 1 0 "PID_SAFETY") (pid:text (pid:pt 110 162) 2.5 "VB/PSV-303" "PID_SAFETY")

  (pid:opcon 45 295 "STEAM / HEATING VAPOR SUPPLY")
  (pid:utility-line (list (pid:pt 58 295) (pid:pt 132 232)) "STEAM TO CR-302" 62 287)
  (pid:control-station 92 266 "TCV-302")
  (pid:opcon 45 92 "STEAM / HEATING VAPOR SUPPLY")
  (pid:utility-line (list (pid:pt 58 92) (pid:pt 132 132)) "STEAM TO CR-303" 62 98)
  (pid:control-station 92 112 "TCV-303")

  (pid:opcon 198 197 "CONDENSATE RETURN")
  (pid:utility-line (list (pid:pt 145 208) (pid:pt 198 197)) "CONDENSATE CR-302" 155 198)
  (pid:opcon 198 112 "CONDENSATE RETURN")
  (pid:utility-line (list (pid:pt 145 123) (pid:pt 198 112)) "CONDENSATE CR-303" 155 113)

  (pid:opcon 275 258 "HOT AIR SUPPLY")
  (pid:utility-line (list (pid:pt 275 250) (pid:pt 285 226)) "HOT AIR DR-302" 288 250)
  (pid:opcon 305 258 "EXHAUST AIR")
  (pid:utility-line (list (pid:pt 292 226) (pid:pt 305 250)) "EXHAUST DR-302" 309 250)
  (pid:opcon 345 258 "COOLING AIR / COOLING WATER")
  (pid:utility-line (list (pid:pt 345 250) (pid:pt 345 226)) "COOLING CL-302" 355 250)

  (pid:opcon 275 173 "HOT AIR SUPPLY")
  (pid:utility-line (list (pid:pt 275 165) (pid:pt 285 141)) "HOT AIR DR-303" 288 166)
  (pid:opcon 305 173 "EXHAUST AIR")
  (pid:utility-line (list (pid:pt 292 141) (pid:pt 305 165)) "EXHAUST DR-303" 309 166)
  (pid:opcon 345 173 "COOLING AIR / COOLING WATER")
  (pid:utility-line (list (pid:pt 345 165) (pid:pt 345 141)) "COOLING CL-303" 355 166)
)


(defun pid:draw-instruments (/)
  ;; Bubbles are intentionally offset from process lines and spaced >= 12 units.
  (foreach inst '((45 250 "LI-302") (60 250 "LT-302") (75 250 "LIC-302") (92 236 "LSH-302") (92 205 "LSL-302")
                  (115 260 "TI-302") (130 260 "TT-302") (145 260 "TIC-302") (170 260 "PI-302") (185 260 "PT-302") (200 260 "PIC-302")
                  (115 185 "AI-302B") (132 185 "AT-302B") (150 185 "AIC-302B")
                  (45 105 "LI-303") (60 105 "LT-303") (75 105 "LIC-303") (92 148 "LSH-303") (92 120 "LSL-303")
                  (115 95 "TI-303") (130 95 "TT-303") (145 95 "TIC-303") (170 160 "PI-303") (185 160 "PT-303") (200 160 "PIC-303")
                  (165 105 "AI-303B") (182 105 "AT-303B") (200 105 "AIC-303B")
                  (175 55 "LI-304") (175 42 "LT-304") (175 29 "LIC-304") (238 58 "LSH-304") (238 45 "LSL-304")
                  (220 238 "XI-302") (235 238 "II-302") (220 153 "XI-303") (235 153 "II-303") (285 238 "TI-312") (345 238 "TI-313") (285 153 "TI-318") (345 153 "TI-319"))
    (pid:inst (car inst) (cadr inst) (caddr inst))
  )
  ;; Dashed control signals, routed with elbows for readability.
  (pid:signal (list (pid:pt 60 250) (pid:pt 75 250) (pid:pt 105 228)))
  (pid:signal (list (pid:pt 130 260) (pid:pt 145 260) (pid:pt 92 266)))
  (pid:signal (list (pid:pt 185 260) (pid:pt 200 260) (pid:pt 145 282)))
  (pid:signal (list (pid:pt 132 185) (pid:pt 150 185)))
  (pid:text (pid:pt 155 190) 2.5 "Brix 88.5-93.8" "PID_TEXT")

  (pid:signal (list (pid:pt 60 105) (pid:pt 75 105) (pid:pt 105 143)))
  (pid:signal (list (pid:pt 130 95) (pid:pt 145 95) (pid:pt 92 112)))
  (pid:signal (list (pid:pt 185 160) (pid:pt 200 160) (pid:pt 190 298)))
  (pid:signal (list (pid:pt 182 105) (pid:pt 200 105)))
  (pid:text (pid:pt 205 108) 2.5 "Brix target 97.0" "PID_TEXT")

  (pid:signal (list (pid:pt 175 42) (pid:pt 175 29) (pid:pt 286 64)))
)


(defun pid:draw-table (x y title headers rows colw rowh txtheight / yy xx i j row total)
  (setq total (apply '+ colw))
  (pid:text (pid:pt x (+ y 4)) 3.0 title "PID_TABLE")
  (setq yy y)
  (pid:rect x (- yy rowh) (+ x total) yy "PID_TABLE")
  (setq xx x i 0)
  (foreach h headers
    (pid:text (pid:pt (+ xx 1) (- yy 5)) txtheight h "PID_TABLE")
    (setq xx (+ xx (nth i colw)) i (1+ i))
    (pid:line (pid:pt xx yy) (pid:pt xx (- yy rowh)) "PID_TABLE"))
  (setq yy (- yy rowh))
  (foreach row rows
    (pid:rect x (- yy rowh) (+ x total) yy "PID_TABLE")
    (setq xx x j 0)
    (foreach cell row
      (pid:mtext (pid:pt (+ xx 1) (- yy 1.5)) (- (nth j colw) 1.5) txtheight cell "PID_TABLE")
      (setq xx (+ xx (nth j colw)) j (1+ j))
      (pid:line (pid:pt xx yy) (pid:pt xx (- yy rowh)) "PID_TABLE"))
    (setq yy (- yy rowh)))
  yy
)

(defun pid:draw-tables (/ lineRows refRows eqRows instRows valveRows y1 y2 y3)
  (setq lineRows '(("S-309" "CF-301" "TK-302" "Molasses A" "Liquid" "60°C" "Atm" "Upstream")
                   ("S-310" "TK-302" "CR-302" "Molasses A Feed" "Liquid" "60°C" "0.235-0.25 bar abs" "B feed")
                   ("S-311" "CR-302" "CF-302" "Massecuite B" "Slurry" "61-64°C" "0.235-0.25 bar abs" "B massecuite")
                   ("S-312" "CF-302" "DR-302" "Wet Sugar B" "Solid/Liq" "60-70°C assumed" "Atm" "To dryer")
                   ("S-313" "DR-302" "CL-302" "Dry Sugar B" "Solid" "T=___°C" "Atm" "Verify")
                   ("S-314" "CL-302" "Outlet" "Grade Sugar B" "Solid" "30-35°C" "Atm" "Product")
                   ("S-315" "CF-302" "TK-303" "Molasses B" "Liquid" "60-70°C assumed" "Atm" "To C stage")
                   ("S-316" "TK-303" "CR-303" "Molasses B Feed" "Liquid" "60-70°C assumed" "0.12-0.13 bar abs" "C feed")
                   ("S-317" "CR-303" "CF-303" "Massecuite C" "Slurry" "60-67°C assumed" "0.12-0.13 bar abs" "C massecuite")
                   ("S-318" "CF-303" "DR-303" "Wet Sugar C" "Solid/Liq" "60-70°C assumed" "Atm" "To dryer")
                   ("S-319" "DR/CL-303" "Outlet" "Grade Sugar C" "Solid" "30-35°C" "Atm" "Product")
                   ("S-320" "CF-303" "TK-304" "Final Molasses" "Liquid" "50-60°C assumed" "Atm" "By-product")))
  (setq refRows '(("Vacuum pan general" "T = 65-85°C; P = 4-9 inHg abs ≈ 0.135-0.305 bar abs")
                  ("CR-302 B crystallizer" "T = 61-64°C; P = 0.235-0.25 bar abs; Vacuum ≈ -0.76 to -0.78 bar(g); Brix 88.5-93.8")
                  ("CR-303 C crystallizer" "T = 60-67°C assumed; P = 0.12-0.13 bar abs; Vacuum ≈ -0.88 to -0.89 bar(g); Brix target 97.0 placeholder")
                  ("CL-302 / CL-303 cooler" "Sugar outlet T = 30-35°C")
                  ("Note" "Literature-based assumed values; verify with actual plant/process data")))
  (setq eqRows '(("TK-302" "Molasses A Tank, level controlled") ("CR-302" "Vacuum Crystallizer B, T/P/Brix controlled") ("CF-302" "Centrifuge B, separates Wet Sugar B and Molasses B") ("DR-302" "Dryer B, hot air drying") ("CL-302" "Cooler B, outlet 30-35°C") ("TK-303" "Molasses B Tank, level controlled") ("CR-303" "Vacuum Crystallizer C, T/P/Brix controlled") ("CF-303" "Centrifuge C, separates Wet Sugar C and Final Molasses") ("DR-303" "Dryer C, hot air drying") ("CL-303" "Cooler C, outlet 30-35°C") ("TK-304" "Final Molasses Tank, level controlled")))
  (setq instRows '(("FCV/PCV/TCV" "Feed, vacuum, and temperature control valves") ("PSV/VB" "Safety / vacuum protection") ("LI/LT/LIC" "Tank level instrumentation") ("TI/TT/TIC" "Temperature instrumentation") ("PI/PT/PIC" "Pressure/vacuum instrumentation") ("AI/AT/AIC" "Brix/concentration analysis instrumentation")))
  (setq valveRows nil)
  (setq y1 (pid:draw-table 455 400 "Line List" '("Line" "From" "To" "Service" "Phase" "T" "P" "Notes") lineRows '(16 22 22 38 24 35 45 32) 9 2.5))
  (setq y2 (pid:draw-table 455 (- y1 12) "Reference Operating Conditions" '("Item" "Condition") refRows '(75 170) 13 2.5))
  (setq y3 (pid:draw-table 455 (- y2 5) "Equipment / Instrument / Valve Summary" '("Tag" "Description") (append eqRows instRows) '(60 185) 6.5 2.1))
)

(defun pid:draw-legend-notes-title (/)
  ;; ISO A1 landscape-proportioned compact border in drawing units.
  (pid:rect 5 5 760 430 "PID_TITLE_BLOCK")
  (pid:rect 12 20 435 320 "PID_BOUNDARY")
  (pid:mtext (pid:pt 18 315) 400 4.0 "P&ID - CRYSTALLIZATION B/C AND FINAL MOLASSES AREA\PAREA 302-319" "PID_TITLE_BLOCK")

  (pid:text (pid:pt 18 35) 3.0 "Legend" "PID_TABLE")
  (pid:line (pid:pt 18 29) (pid:pt 38 29) "PID_PROCESS_LINE") (pid:text (pid:pt 42 28) 2.5 "Process line" "PID_TEXT")
  (pid:line (pid:pt 18 23) (pid:pt 38 23) "PID_UTILITY_LINE") (pid:text (pid:pt 42 22) 2.5 "Utility/vapor/vacuum line" "PID_TEXT")
  (pid:line (pid:pt 18 17) (pid:pt 38 17) "PID_SIGNAL") (pid:text (pid:pt 42 16) 2.5 "Instrument signal line" "PID_TEXT")
  (pid:insert "BLK_PID_MANUAL_VALVE" (pid:pt 150 29) 1 1 0 "PID_VALVE") (pid:text (pid:pt 158 28) 2.5 "Manual valve" "PID_TEXT")
  (pid:insert "BLK_PID_CONTROL_VALVE" (pid:pt 150 17) 1 1 0 "PID_VALVE") (pid:text (pid:pt 158 16) 2.5 "Control valve" "PID_TEXT")
  (pid:insert "BLK_PID_INSTRUMENT_BUBBLE" (pid:pt 245 29) 1 1 0 "PID_INSTRUMENT") (pid:text (pid:pt 253 28) 2.5 "Instrument bubble" "PID_TEXT")
  (pid:insert "BLK_PID_OFFPAGE_CONNECTOR" (pid:pt 245 17) 0.8 0.8 0 "PID_BOUNDARY") (pid:text (pid:pt 260 16) 2.5 "Off-page connector" "PID_TEXT")

  (pid:mtext (pid:pt 18 112) 340 2.8 (strcat "General Notes:\P1. Conceptual educational 2D P&ID; not an intelligent Plant 3D database object.\P2. Instrument tagging follows ISA 5.1-style conventions.\P3. Symbols follow AutoCAD Plant 3D P&ID ISO-style / ISO 10628-style representation.\P4. All T, P, vacuum, and Brix values are literature-based assumptions and must be verified with actual plant/process data.\P5. No nozzle size, pipe class, material, valve class, or relief sizing is finalized.") "PID_TEXT")
  (pid:rect 455 10 755 70 "PID_TITLE_BLOCK")
  (pid:mtext (pid:pt 460 66) 290 2.6 "Drawing Title: P&ID - Crystallization B/C and Final Molasses Area\PProject: Sugar Plant Process\PDrawing No: PID-302-319     Revision: Rev. 0\PPrepared by: Bintang Mizar Molawan     Scale: NTS\PStandard: AutoCAD Plant 3D P&ID ISO-style / ISA 5.1-style\PStatus: Conceptual Educational Drawing" "PID_TITLE_BLOCK")
)

(defun pid:clear-modelspace (/ ss idx ent)
  (setq ss (ssget "_X" (list (cons 410 "Model"))))
  (if ss
    (progn
      (setq idx 0)
      (repeat (sslength ss)
        (setq ent (ssname ss idx))
        (if ent (entdel ent))
        (setq idx (1+ idx))
      )
    )
  )
)

(defun pid:run (/ *error* oldcmdecho oldosmode)
  (setq oldcmdecho (getvar "CMDECHO"))
  (setq oldosmode (getvar "OSMODE"))
  (defun *error* (msg)
    (if oldosmode (setvar "OSMODE" oldosmode))
    (if oldcmdecho (setvar "CMDECHO" oldcmdecho))
    (vl-catch-all-apply 'vl-cmdf (list "_.UNDO" "_E"))
    (princ (strcat "\nPIDCRYSTAL2D error: " msg))
    (princ)
  )
  (setvar "CMDECHO" 0)
  (setvar "OSMODE" 0)
  (vl-cmdf "_.UNDO" "_BE")
  (pid:setup-layers)
  (pid:clear-modelspace)
  (pid:define-blocks)
  (pid:draw-legend-notes-title)
  (pid:draw-equipment)
  (pid:draw-process)
  (pid:draw-utilities)
  (pid:draw-instruments)
  (pid:draw-tables)
  (vl-cmdf "_.ZOOM" "_E")
  (vl-cmdf "_.UNDO" "_E")
  (setvar "OSMODE" oldosmode)
  (setvar "CMDECHO" oldcmdecho)
  (princ "\nPIDCRYSTAL2D complete: compact 2D P&ID drawn in model space. ")
  (princ)
)

(defun c:PIDCRYSTAL2D () (pid:run))

(princ "\nLoaded crystallization_area_pid_2d.lsp. Run PIDCRYSTAL2D to draw compact 2D P&ID. ")
(princ)
