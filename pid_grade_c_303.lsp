;;; pid_grade_c_303.lsp
;;; Standalone 2D conceptual P&ID generator for AutoCAD / AutoCAD Plant 3D 2025.
;;; Command: PIDGRADEC
;;; This file creates manual 2D P&ID geometry only; no Plant 3D database objects or 3D solids.

(vl-load-com)
(setq *pid-note* "Literature-based assumed value; verify with actual plant/process data.")

(defun pid:pt (x y) (list (float x) (float y) 0.0))
(defun pid:set-layer (lay) (setvar "CLAYER" lay))
(defun pid:ensure-linetype (lt /)
  (if (and lt (/= (strcase lt) "CONTINUOUS") (not (tblsearch "LTYPE" lt)))
    (vl-catch-all-apply 'vl-cmdf (list "_.-LINETYPE" "_Load" lt "acad.lin" ""))))
(defun pid:lw-code (lw / val) (setq val (fix (+ 0.5 (* 100.0 (atof lw))))) (if (> val 0) val -3))
(defun pid:replace-dxf (code value data / found out pair)
  (setq found nil out nil)
  (foreach pair data
    (if (= (car pair) code) (progn (setq out (cons (cons code value) out)) (setq found T)) (setq out (cons pair out))))
  (if found (reverse out) (reverse (cons (cons code value) out))))
(defun pid:make-layer (name color ltype lw / obj data)
  (pid:ensure-linetype ltype)
  (if (setq obj (tblobjname "LAYER" name))
    (progn
      (setq data (entget obj))
      (setq data (pid:replace-dxf 62 color data))
      (setq data (pid:replace-dxf 6 ltype data))
      (setq data (pid:replace-dxf 370 (pid:lw-code lw) data))
      (entmod data) (entupd obj))
    (entmakex (list '(0 . "LAYER") '(100 . "AcDbSymbolTableRecord") '(100 . "AcDbLayerTableRecord")
                    (cons 2 name) '(70 . 0) (cons 62 color) (cons 6 ltype) (cons 370 (pid:lw-code lw))))))
(defun pid:setup-layers (/)
  ;; Dark-background readable colors: equipment/text white, process cyan, utility green, signal magenta, valve red, safety orange, border gray.
  (pid:make-layer "PID_EQUIPMENT" 7 "CONTINUOUS" "0.30")
  (pid:make-layer "PID_PROCESS_LINE" 4 "CONTINUOUS" "0.35")
  (pid:make-layer "PID_UTILITY_LINE" 3 "DASHED" "0.25")
  (pid:make-layer "PID_INSTRUMENT" 6 "CONTINUOUS" "0.18")
  (pid:make-layer "PID_SIGNAL" 6 "DASHED" "0.18")
  (pid:make-layer "PID_VALVE" 1 "CONTINUOUS" "0.25")
  (pid:make-layer "PID_TEXT" 7 "CONTINUOUS" "0.18")
  (pid:make-layer "PID_TABLE" 7 "CONTINUOUS" "0.18")
  (pid:make-layer "PID_SAFETY" 30 "CONTINUOUS" "0.25")
  (pid:make-layer "PID_BOUNDARY" 8 "CONTINUOUS" "0.25")
  (pid:make-layer "PID_TITLE_BLOCK" 8 "CONTINUOUS" "0.25"))
(defun pid:line (p1 p2 lay /) (pid:set-layer lay) (entmakex (list '(0 . "LINE") (cons 8 lay) (cons 10 p1) (cons 11 p2))))
(defun pid:circle (cen rad lay /) (pid:set-layer lay) (entmakex (list '(0 . "CIRCLE") (cons 8 lay) (cons 10 cen) (cons 40 rad))))
(defun pid:arc (cen rad a1 a2 lay /) (pid:set-layer lay) (entmakex (list '(0 . "ARC") (cons 8 lay) (cons 10 cen) (cons 40 rad) (cons 50 a1) (cons 51 a2))))
(defun pid:pline (pts lay closed / data)
  (pid:set-layer lay)
  (setq data (list '(0 . "LWPOLYLINE") '(100 . "AcDbEntity") (cons 8 lay) '(100 . "AcDbPolyline") (cons 90 (length pts)) (cons 70 (if closed 1 0))))
  (foreach p pts (setq data (append data (list (cons 10 (list (car p) (cadr p)))))))
  (entmakex data))
(defun pid:rect (x1 y1 x2 y2 lay /) (pid:pline (list (pid:pt x1 y1) (pid:pt x2 y1) (pid:pt x2 y2) (pid:pt x1 y2)) lay T))
(defun pid:text (pt h str lay /) (pid:set-layer lay) (entmakex (list '(0 . "TEXT") (cons 8 lay) (cons 10 pt) (cons 40 h) (cons 1 str) '(50 . 0.0) '(7 . "Standard") '(72 . 0) '(73 . 0))))
(defun pid:mtext (pt w h str lay /) (pid:set-layer lay) (entmakex (list '(0 . "MTEXT") (cons 8 lay) (cons 10 pt) (cons 40 h) (cons 41 w) (cons 1 str) '(7 . "Standard") '(71 . 1))))

(defun pid:block-start (name / obj made)
  (if (setq obj (tblobjname "BLOCK" name)) (vl-catch-all-apply 'entdel (list obj)))
  (if (not (tblsearch "BLOCK" name)) (setq made (entmakex (list '(0 . "BLOCK") (cons 2 name) '(70 . 0) (cons 10 (pid:pt 0 0))))))
  (if made T nil))
(defun pid:block-end () (entmakex '((0 . "ENDBLK"))))
(defun pid:define-blocks (/)
  (if (pid:block-start "BLK_PID_VERTICAL_TANK") (progn (pid:rect -7 -11 7 11 "PID_EQUIPMENT") (pid:arc (pid:pt 0 11) 7 0 pi "PID_EQUIPMENT") (pid:arc (pid:pt 0 -11) 7 pi (* 2 pi) "PID_EQUIPMENT") (pid:line (pid:pt -5 -11) (pid:pt -8 -15) "PID_EQUIPMENT") (pid:line (pid:pt 5 -11) (pid:pt 8 -15) "PID_EQUIPMENT") (pid:block-end)))
  (if (pid:block-start "BLK_PID_VACUUM_CRYSTALLIZER") (progn (pid:rect -9 -12 9 12 "PID_EQUIPMENT") (pid:arc (pid:pt 0 12) 9 0 pi "PID_EQUIPMENT") (pid:arc (pid:pt 0 -12) 9 pi (* 2 pi) "PID_EQUIPMENT") (pid:line (pid:pt -9 3) (pid:pt 9 3) "PID_EQUIPMENT") (pid:line (pid:pt -9 -4) (pid:pt 9 -4) "PID_EQUIPMENT") (pid:line (pid:pt 0 20) (pid:pt 0 12) "PID_EQUIPMENT") (pid:block-end)))
  (if (pid:block-start "BLK_PID_CENTRIFUGE") (progn (pid:circle (pid:pt 0 0) 10 "PID_EQUIPMENT") (pid:circle (pid:pt 0 0) 5 "PID_EQUIPMENT") (pid:line (pid:pt -8 -6) (pid:pt 8 6) "PID_EQUIPMENT") (pid:line (pid:pt -8 6) (pid:pt 8 -6) "PID_EQUIPMENT") (pid:block-end)))
  (if (pid:block-start "BLK_PID_DRYER") (progn (pid:rect -13 -6 13 6 "PID_EQUIPMENT") (pid:line (pid:pt -10 -6) (pid:pt -5 6) "PID_EQUIPMENT") (pid:line (pid:pt 0 -6) (pid:pt 5 6) "PID_EQUIPMENT") (pid:line (pid:pt 8 -6) (pid:pt 13 6) "PID_EQUIPMENT") (pid:block-end)))
  (if (pid:block-start "BLK_PID_COOLER") (progn (pid:rect -11 -6 11 6 "PID_EQUIPMENT") (pid:line (pid:pt -11 0) (pid:pt 11 0) "PID_EQUIPMENT") (pid:line (pid:pt -5 -6) (pid:pt -5 6) "PID_EQUIPMENT") (pid:line (pid:pt 5 -6) (pid:pt 5 6) "PID_EQUIPMENT") (pid:block-end)))
  (if (pid:block-start "BLK_PID_MANUAL_VALVE") (progn (pid:pline (list (pid:pt -4 -3) (pid:pt 0 0) (pid:pt -4 3)) "PID_VALVE" T) (pid:pline (list (pid:pt 4 -3) (pid:pt 0 0) (pid:pt 4 3)) "PID_VALVE" T) (pid:block-end)))
  (if (pid:block-start "BLK_PID_CONTROL_VALVE") (progn (pid:pline (list (pid:pt -5 -3) (pid:pt 0 0) (pid:pt -5 3)) "PID_VALVE" T) (pid:pline (list (pid:pt 5 -3) (pid:pt 0 0) (pid:pt 5 3)) "PID_VALVE" T) (pid:line (pid:pt 0 0) (pid:pt 0 8) "PID_VALVE") (pid:circle (pid:pt 0 10) 2.5 "PID_VALVE") (pid:block-end)))
  (if (pid:block-start "BLK_PID_INSTRUMENT_BUBBLE") (progn (pid:circle (pid:pt 0 0) 5 "PID_INSTRUMENT") (pid:block-end)))
  (if (pid:block-start "BLK_PID_OFFPAGE_CONNECTOR") (progn (pid:pline (list (pid:pt -12 -5) (pid:pt 7 -5) (pid:pt 13 0) (pid:pt 7 5) (pid:pt -12 5)) "PID_BOUNDARY" T) (pid:block-end)))
  (if (pid:block-start "BLK_PID_FLOW_ARROW") (progn (pid:pline (list (pid:pt -3 -2) (pid:pt 4 0) (pid:pt -3 2)) "PID_PROCESS_LINE" T) (pid:block-end)))
  (if (pid:block-start "BLK_PID_DRAIN") (progn (pid:line (pid:pt 0 0) (pid:pt 0 -7) "PID_SAFETY") (pid:pline (list (pid:pt -4 -7) (pid:pt 4 -7) (pid:pt 0 -11)) "PID_SAFETY" T) (pid:block-end)))
  (if (pid:block-start "BLK_PID_VENT") (progn (pid:line (pid:pt 0 0) (pid:pt 0 7) "PID_SAFETY") (pid:arc (pid:pt 0 9) 2 0 pi "PID_SAFETY") (pid:block-end)))
  (if (pid:block-start "BLK_PID_PSV") (progn (pid:circle (pid:pt 0 0) 4 "PID_SAFETY") (pid:pline (list (pid:pt -3 -1) (pid:pt 0 3) (pid:pt 3 -1)) "PID_SAFETY" T) (pid:block-end)))
  (if (pid:block-start "BLK_PID_SAMPLE_POINT") (progn (pid:circle (pid:pt 0 0) 2 "PID_SAFETY") (pid:line (pid:pt 0 0) (pid:pt 0 -6) "PID_SAFETY") (pid:block-end))))

(defun pid:insert (name pt sx sy rot lay /) (pid:set-layer lay) (entmakex (list '(0 . "INSERT") (cons 8 lay) (cons 2 name) (cons 10 pt) (cons 41 sx) (cons 42 sy) (cons 43 1.0) (cons 50 rot))))
(defun pid:tag (x y tag name /) (pid:text (pid:pt (- x 10) (- y 18)) 3.0 tag "PID_TEXT") (pid:text (pid:pt (- x 18) (- y 23)) 2.5 name "PID_TEXT"))
(defun pid:inst (x y tag /) (pid:insert "BLK_PID_INSTRUMENT_BUBBLE" (pid:pt x y) 1 1 0 "PID_INSTRUMENT") (pid:text (pid:pt (- x 4.5) (- y 1.3)) 2.2 tag "PID_INSTRUMENT"))
(defun pid:valve (x y tag ctrl /) (pid:insert (if ctrl "BLK_PID_CONTROL_VALVE" "BLK_PID_MANUAL_VALVE") (pid:pt x y) 1 1 0 "PID_VALVE") (pid:text (pid:pt (+ x 5) (+ y 4)) 2.2 tag "PID_VALVE"))
(defun pid:opcon (x y txt /) (pid:insert "BLK_PID_OFFPAGE_CONNECTOR" (pid:pt x y) 1 1 0 "PID_BOUNDARY") (pid:mtext (pid:pt (- x 11) (+ y 3)) 55 2.5 txt "PID_TEXT"))
(defun pid:arrow-at (p1 p2 / ang) (setq ang (atan (- (cadr p2) (cadr p1)) (- (car p2) (car p1)))) (pid:insert "BLK_PID_FLOW_ARROW" (pid:pt (/ (+ (car p1) (car p2)) 2.0) (/ (+ (cadr p1) (cadr p2)) 2.0)) 1 1 ang "PID_PROCESS_LINE"))
(defun pid:path (pts lay / p1 p2) (setq p1 nil) (foreach p2 pts (if p1 (pid:line p1 p2 lay)) (setq p1 p2)))
(defun pid:process (pts lineNo service lx ly / p1 p2) (pid:path pts "PID_PROCESS_LINE") (setq p1 (car pts) p2 (cadr pts)) (pid:arrow-at p1 p2) (pid:text (pid:pt lx ly) 2.5 (strcat lineNo "  " service) "PID_TEXT"))
(defun pid:utility (pts label lx ly /) (pid:path pts "PID_UTILITY_LINE") (if (> (length pts) 1) (pid:arrow-at (car pts) (cadr pts))) (pid:text (pid:pt lx ly) 2.5 label "PID_TEXT"))
(defun pid:signal (pts /) (pid:path pts "PID_SIGNAL"))
(defun pid:table (x y title headers rows colw rowh th / total yy xx i j row)
  (setq total (apply '+ colw)) (pid:text (pid:pt x (+ y 4)) 3.0 title "PID_TABLE")
  (setq yy y) (pid:rect x (- yy rowh) (+ x total) yy "PID_TABLE") (setq xx x i 0)
  (foreach h headers (pid:text (pid:pt (+ xx 1) (- yy 5)) th h "PID_TABLE") (setq xx (+ xx (nth i colw)) i (1+ i)) (pid:line (pid:pt xx yy) (pid:pt xx (- yy rowh)) "PID_TABLE"))
  (setq yy (- yy rowh))
  (foreach row rows (pid:rect x (- yy rowh) (+ x total) yy "PID_TABLE") (setq xx x j 0)
    (foreach cell row (pid:mtext (pid:pt (+ xx 1) (- yy 1)) (- (nth j colw) 2) th cell "PID_TABLE") (setq xx (+ xx (nth j colw)) j (1+ j)) (pid:line (pid:pt xx yy) (pid:pt xx (- yy rowh)) "PID_TABLE"))
    (setq yy (- yy rowh))) yy)
(defun pid:legend (x y /)
  (pid:text (pid:pt x y) 3.0 "Legend" "PID_TABLE")
  (pid:line (pid:pt x (- y 6)) (pid:pt (+ x 18) (- y 6)) "PID_PROCESS_LINE") (pid:text (pid:pt (+ x 22) (- y 7)) 2.3 "Process line" "PID_TEXT")
  (pid:line (pid:pt x (- y 12)) (pid:pt (+ x 18) (- y 12)) "PID_UTILITY_LINE") (pid:text (pid:pt (+ x 22) (- y 13)) 2.3 "Utility line" "PID_TEXT")
  (pid:line (pid:pt x (- y 18)) (pid:pt (+ x 18) (- y 18)) "PID_SIGNAL") (pid:text (pid:pt (+ x 22) (- y 19)) 2.3 "Signal line" "PID_TEXT")
  (pid:insert "BLK_PID_MANUAL_VALVE" (pid:pt (+ x 4) (- y 27)) 1 1 0 "PID_VALVE") (pid:text (pid:pt (+ x 22) (- y 29)) 2.3 "Manual valve" "PID_TEXT")
  (pid:insert "BLK_PID_INSTRUMENT_BUBBLE" (pid:pt (+ x 4) (- y 38)) 1 1 0 "PID_INSTRUMENT") (pid:text (pid:pt (+ x 22) (- y 40)) 2.3 "Instrument bubble" "PID_TEXT"))
(defun pid:title-block (title dwg /)
  (pid:rect 5 5 760 365 "PID_TITLE_BLOCK")
  (pid:rect 452 8 755 62 "PID_TITLE_BLOCK")
  (pid:mtext (pid:pt 458 58) 292 2.5 (strcat "Drawing Title: " title "\\PProject: Sugar Plant Process\\PDrawing No: " dwg "     Revision: Rev. 0\\PPrepared by: Bintang Mizar Molawan     Scale: NTS\\PStandard: AutoCAD Plant 3D P&ID ISO-style / ISA 5.1-style\\PStatus: Conceptual Educational Drawing") "PID_TITLE_BLOCK")
  (pid:mtext (pid:pt 18 353) 420 5.0 title "PID_TITLE_BLOCK")
  (pid:mtext (pid:pt 18 36) 420 2.3 "This P&ID is a conceptual educational drawing. Instrumentation tagging follows ISA 5.1-style conventions. Equipment and line symbols follow AutoCAD Plant 3D P&ID ISO-style / ISO 10628-style representation. Operating values are literature-based assumptions and must be verified with actual plant/process data." "PID_TEXT")
  (pid:legend 18 78))
(defun pid:clear (/ ss i e) (setq ss (ssget "_X" (list (cons 410 "Model")))) (if ss (progn (setq i 0) (repeat (sslength ss) (setq e (ssname ss i)) (if e (entdel e)) (setq i (1+ i))))))

(defun pid:draw (/)
  (pid:title-block "P&ID - Grade Sugar C Crystallization Area" "PID-303-C")
  ;; Equipment row and off-page connectors.
  (pid:opcon 20 120 "FROM GRADE B AREA / CF-302 / MOLASSES B")
  (pid:insert "BLK_PID_VERTICAL_TANK" (pid:pt 70 120) 1 1 0 "PID_EQUIPMENT") (pid:tag 70 120 "TK-303" "Molasses B Tank")
  (pid:insert "BLK_PID_VACUUM_CRYSTALLIZER" (pid:pt 140 120) 1 1 0 "PID_EQUIPMENT") (pid:tag 140 120 "CR-303" "Vacuum Crystallizer C")
  (pid:insert "BLK_PID_CENTRIFUGE" (pid:pt 210 120) 1 1 0 "PID_EQUIPMENT") (pid:tag 210 120 "CF-303" "Centrifuge C")
  (pid:insert "BLK_PID_DRYER" (pid:pt 280 120) 1 1 0 "PID_EQUIPMENT") (pid:tag 280 120 "DR-303" "Dryer C")
  (pid:insert "BLK_PID_COOLER" (pid:pt 340 120) 1 1 0 "PID_EQUIPMENT") (pid:tag 340 120 "CL-303" "Cooler C")
  (pid:opcon 405 120 "TO GRADE SUGAR C")
  (pid:opcon 280 70 "TO FINAL MOLASSES AREA / TK-304")

  ;; Process lines with arrows and labels.
  (pid:process (list (pid:pt 33 120) (pid:pt 61 120)) "S-315" "Molasses B" 35 131) (pid:valve 48 120 "HV-303A" nil)
  (pid:process (list (pid:pt 79 120) (pid:pt 131 120)) "S-316" "Molasses B Feed" 86 133) (pid:valve 95 120 "HV-303B" nil) (pid:valve 118 120 "FCV-303" T)
  (pid:process (list (pid:pt 149 120) (pid:pt 200 120)) "S-317" "Massecuite C" 155 133) (pid:valve 174 120 "HV-303C" nil)
  (pid:process (list (pid:pt 220 120) (pid:pt 267 120)) "S-318" "Wet Sugar C" 225 133)
  (pid:process (list (pid:pt 293 120) (pid:pt 329 120)) "S-319" "Dry Sugar C" 298 133)
  (pid:process (list (pid:pt 351 120) (pid:pt 392 120)) "S-319" "Grade Sugar C" 355 133)
  (pid:process (list (pid:pt 210 110) (pid:pt 210 70) (pid:pt 267 70)) "S-320" "Final Molasses" 218 83)

  ;; Instruments are offset from equipment for readability.
  (foreach inst '((50 153 "LI-303") (65 153 "LT-303") (80 153 "LIC-303") (92 133 "LSH-303") (92 105 "LSL-303")
                  (112 162 "TI-303") (127 162 "TT-303") (142 162 "TIC-303") (165 162 "PI-303") (180 162 "PT-303") (195 162 "PIC-303")
                  (114 88 "AI-303B") (132 88 "AT-303B") (150 88 "AIC-303B")
                  (105 142 "FT-303") (120 142 "FIC-303") (210 142 "XI-303") (225 142 "II-303")
                  (280 142 "TI-318") (295 142 "TT-318") (340 142 "TI-319"))
    (pid:inst (car inst) (cadr inst) (caddr inst)))
  ;; Dashed control/signal lines.
  (pid:signal (list (pid:pt 65 153) (pid:pt 80 153) (pid:pt 118 130)))
  (pid:signal (list (pid:pt 105 142) (pid:pt 120 142) (pid:pt 118 130)))
  (pid:signal (list (pid:pt 180 162) (pid:pt 195 162) (pid:pt 140 190)))
  (pid:signal (list (pid:pt 127 162) (pid:pt 142 162) (pid:pt 92 180)))
  (pid:signal (list (pid:pt 132 88) (pid:pt 150 88) (pid:pt 120 142)))

  ;; Utility and safety details.
  (pid:opcon 140 215 "TO VACUUM SYSTEM / CONDENSER")
  (pid:utility (list (pid:pt 140 140) (pid:pt 140 202)) "VAPOR / VACUUM" 148 188) (pid:valve 140 188 "PCV-303" T)
  (pid:insert "BLK_PID_PSV" (pid:pt 125 145) 1 1 0 "PID_SAFETY") (pid:text (pid:pt 112 151) 2.3 "PSV/VB-303" "PID_SAFETY")
  (pid:opcon 55 205 "STEAM / HEATING VAPOR")
  (pid:utility (list (pid:pt 68 205) (pid:pt 130 132)) "STEAM" 74 195) (pid:valve 92 180 "TCV-303" T)
  (pid:opcon 180 92 "CONDENSATE RETURN") (pid:utility (list (pid:pt 140 108) (pid:pt 180 92)) "CONDENSATE" 148 96)
  (pid:opcon 272 160 "HOT AIR SUPPLY") (pid:utility (list (pid:pt 272 154) (pid:pt 280 126)) "HOT AIR" 284 154)
  (pid:opcon 305 160 "EXHAUST AIR") (pid:utility (list (pid:pt 286 126) (pid:pt 305 154)) "EXHAUST" 309 154)
  (pid:opcon 342 160 "COOLING AIR / WATER") (pid:utility (list (pid:pt 342 154) (pid:pt 340 126)) "COOLING" 352 154)
  (pid:insert "BLK_PID_DRAIN" (pid:pt 70 107) 1 1 0 "PID_SAFETY") (pid:text (pid:pt 75 98) 2.3 "DV-303" "PID_SAFETY")
  (pid:insert "BLK_PID_VENT" (pid:pt 148 141) 1 1 0 "PID_SAFETY") (pid:text (pid:pt 153 148) 2.3 "VV-303" "PID_SAFETY")
  (pid:insert "BLK_PID_SAMPLE_POINT" (pid:pt 104 130) 1 1 0 "PID_SAFETY") (pid:text (pid:pt 108 135) 2.3 "SP-303" "PID_SAFETY")

  ;; Compact, filled tables only for this drawing.
  (pid:table 455 340 "Equipment List" '("Tag" "Name" "Service") '(("TK-303" "Molasses B Tank" "B molasses receiver") ("CR-303" "Vacuum Crystallizer C" "C massecuite crystallization") ("CF-303" "Centrifuge C" "Separates wet sugar C/final molasses") ("DR-303" "Dryer C" "Wet Sugar C drying") ("CL-303" "Cooler C" "Dry Sugar C cooling")) '(35 65 135) 8 2.1)
  (pid:table 455 285 "Line List" '("Line" "From" "To" "Service" "Notes") '(("S-315" "CF-302" "TK-303" "Molasses B" "From Grade B") ("S-316" "TK-303" "CR-303" "Feed" "60-70°C assumed") ("S-317" "CR-303" "CF-303" "Massecuite C" "60-67°C assumed") ("S-318" "CF-303" "DR-303" "Wet Sugar C" "To dryer") ("S-319" "DR/CL-303" "Outlet" "Grade Sugar C" "30-35°C") ("S-320" "CF-303" "TK-304" "Final Molasses" "Off-page to final molasses")) '(24 38 38 70 75) 8 2.0)
  (pid:table 455 214 "Instrument List" '("Tag" "Variable" "Function") '(("LI/LT/LIC-303" "Level" "Tank level control") ("TI/TT/TIC-303" "Temp" "Heating control") ("PI/PT/PIC-303" "Pressure" "Vacuum control") ("AI/AT/AIC-303B" "Analysis" "Brix control") ("XI/II-303" "Status/current" "Centrifuge monitor") ("TI/TT-318; TI-319" "Temp" "Dryer/cooler monitor")) '(62 48 135) 8 2.0)
  (pid:table 455 158 "Valve List" '("Tag" "Type" "Function") '(("HV-303A/B/C" "Manual" "Isolation") ("FCV-303" "Control" "Feed flow") ("PCV-303" "Control" "Vacuum") ("TCV-303" "Control" "Steam") ("DV/VV/PSV" "Safety" "Drain/vent/protection") ("SP-303" "Sample" "Molasses B line")) '(46 45 154) 8 2.0)
  (pid:table 455 96 "Operating Condition Notes" '("Item" "Basis" "Condition") '(("CR-303" "Assumed" "T=60-67°C; P=0.12-0.13 bar abs; Brix target 97.0") ("CL-303" "Assumed" "Sugar outlet 30-35°C") ("Note" "Assumption" "Literature-based assumed value; verify with actual plant/process data")) '(46 45 154) 8 2.0)
)

(defun pid:run (/ *error* oldcmdecho oldosmode)
  (setq oldcmdecho (getvar "CMDECHO")) (setq oldosmode (getvar "OSMODE"))
  (defun *error* (msg) (if oldosmode (setvar "OSMODE" oldosmode)) (if oldcmdecho (setvar "CMDECHO" oldcmdecho)) (vl-catch-all-apply 'vl-cmdf (list "_.UNDO" "_E")) (princ (strcat "\nPIDGRADEC error: " msg)) (princ))
  (setvar "CMDECHO" 0) (setvar "OSMODE" 0) (vl-cmdf "_.UNDO" "_BE")
  (pid:setup-layers) (pid:clear) (pid:define-blocks) (pid:draw)
  (vl-cmdf "_.ZOOM" "_E") (vl-cmdf "_.UNDO" "_E")
  (setvar "OSMODE" oldosmode) (setvar "CMDECHO" oldcmdecho)
  (princ "\nPIDGRADEC complete. ") (princ))
(defun c:PIDGRADEC () (pid:run))
(princ "\nLoaded pid_grade_c_303.lsp. Run PIDGRADEC. ") (princ)
